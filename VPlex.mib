--------------------------------------------------------------------------
-- Copyright (c) 2009 - 2010 All rights reserved by
--
-- EMC Corporation
-- Hopkinton, MA 01748 USA 
--
-- This software is furnished under a license and may be used and copied
-- inclusion of the above copyright notice. This software or any other
-- only in accordance with the terms of such license and with the
-- copies thereof may not be provided or otherwise made available to any
-- other person. No title to and ownership of the software is hereby
-- transferred.
--
-- The information in this software is subject to change without notice
-- and should not be construed as a commitment by EMC Corporation.
--
-- EMC Corporation assumes no responsibility for the use or reliability
-- of this software.
--
----------------------------------------------------------------------------
--
-- V-Plex Product 
--
----------------------------------------------------------------------------
----------------------------------------------------------------------------
-- 
-- EMC Technical Contact
--
-- Neha Siddha Siddha_Neha@emc.com, Jessica Schnieder, schnieder_jessica@emc.com
--
----------------------------------------------------------------------------


VPLEX-MIB DEFINITIONS ::= BEGIN

IMPORTS
    MODULE-IDENTITY, enterprises, OBJECT-TYPE, NOTIFICATION-TYPE
        FROM SNMPv2-SMI;

vplex MODULE-IDENTITY
    LAST-UPDATED "201002020925Z"
    ORGANIZATION "EMC Corporation"
    CONTACT-INFO    
	   "postal:   EMC Corporation 
                    176 South Street
                    Hopkinton, MA 01748 USA
          phone:    1-800-424-EMC2 
          web:	  www.emc.com
          email:    support@emc.com"
    DESCRIPTION  "The EMC V-Plex MIB tree."
    REVISION     "201002020925z"
    DESCRIPTION  "Second draft"
-- 1.3.6.1.4.1.1139.21 -- ::= { enterprises 1139 21 }

-- top-level structures 
vplexTraps OBJECT IDENTIFIER ::= { vplex 0 }
vplexEvent OBJECT IDENTIFIER ::= { vplex 1 }


-- event fields
vplexLocale ::= TEXTUAL-CONVENTION
    STATUS      current
    DESCRIPTION "Event locale indicates the scope of the event. 
                 An event with director locale affects only one director,
                 an event with cluster locale affects the functionality of an entire cluster,
                 and a locale of plex indicates that the functionality of the plex is affected."
    SYNTAX      INTEGER {
                  director(0),
                  cluster(1),
                  plex(2)
                }

vplexEventSource OBJECT-TYPE
    SYNTAX      OCTET STRING
    MAX-ACCESS  accessible-for-notify
    STATUS      current
    DESCRIPTION "Serial number of the V-Plex cluster generating this event."
    ::= { vplexEvent 1 }

vplexEventLocale OBJECT-TYPE
    SYNTAX 	VPlexLocale
    MAX-ACCESS	accessible-for-notify
    STATUS	current
    DESCRIPTION ""
    ::= { vplexEvent 2 }

vplexEventCode OBJECT-TYPE
    SYNTAX      OCTET STRING
    MAX-ACCESS  accessible-for-notify
    STATUS      current
    DESCRIPTION "Unique id, identifying the event."
    ::= { vplexEvent 3 }

vplexEventRcaAndRemedy OBJECT-TYPE
    SYNTAX      OCTET STRING
    MAX-ACCESS  accessible-for-notify
    STATUS      current
    DESCRIPTION "Root cause analysis and remedy for this event."
    ::= { vplexEvent 4 }

vplexEventDescription OBJECT-TYPE
    SYNTAX       OCTET STRING
    MAX-ACCESS   accessible-for-notify
    STATUS       current
    DESCRIPTION  "Description of the event."
    ::= { vplexEvent 5 }


-- trap types

vplexNotificationCritical NOTIFICATION-TYPE
    OBJECTS     { vplexEventSource,
                  vplexEventLocale,
                  vplexEventCode,
                  vplexEventRcaAndRemedy,
                  vplexEventDescription }
    STATUS	current
    DESCRIPTION "This notification is generated by a V-Plex cluster 
                 to indicate an emergency. An emergency indicates the 
                 system is or will be unusable if the situation is not resolved."
    ::= { vplexTraps 1 }

vplexNotificationError NOTIFICATION-TYPE
    OBJECTS     { vplexEventSource,
                  vplexEventLocale,
                  vplexEventCode,
                  vplexEventRcaAndRemedy,
                  vplexEventDescription }
    STATUS	current
    DESCRIPTION "This notification is generated by a V-Plex cluster 
                 to indicate an error."
    ::= { vplexTraps 2 }

vplexNotificationWarning NOTIFICATION-TYPE
    OBJECTS     { vplexEventSource,
                  vplexEventLocale,
                  vplexEventCode,
                  vplexEventRcaAndRemedy,
                  vplexEventDescription }
    STATUS	current
    DESCRIPTION "This notification is generated by a V-Plex cluster
                 to warn the user about a recoverable error."
    ::= { vplexTraps 3 }

vplexNotificationInfo NOTIFICATION-TYPE
    OBJECTS     { vplexEventSource,
                  vplexEventLocale,
                  vplexEventCode,
                  vplexEventRcaAndRemedy,
                  vplexEventDescription }
    STATUS	current
    DESCRIPTION "This notification is generated by a V-Plex cluster
                 to notify the user about an informational event."
    ::= { vplexTraps 4 }

END
